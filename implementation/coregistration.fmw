FME workspace coregistration.fmw

Parameters:
- SourceDataset_CITYGML = D:\projects\PassageFinder\data\raw\CityGML\TUM Munich\TUM Munich.gml   # Source CityGML File(s)
- SourceDataset_LAS = D:\projects\PassageFinder\PCDtoWGS84\data\processed\inUTM\Laser1.las   # Source ASPRS LAS File(s)
- Accuracy = 1   # Accuracy of rough georegistration
- DestDataset_LAS_2 = D:\projects\PassageFinder\PointCloudGeoregistration\data\processed\georeferencingForPaper\munich   # Destination ASPRS LAS Folder
- SourceDataset_LAS_4 = D:\projects\PassageFinder\PCDtoWGS84\data\processed\inUTM\Laser2.las   # Source ASPRS LAS File(s)
- CityModelForReference = D:\projects\PassageFinder\PointCloudGeoregistration\data\processed\citygmlToBeReferenced   # Folder
- MLSforRegistration = D:\projects\PassageFinder\PointCloudGeoregistration\data\processed\mlsToBeRegistered   # Folder
- tmpXYZbldInliers = D:\projects\PassageFinder\PointCloudGeoregistration\data\processed\mlsRANSACinliers   # Select a path for found inliers within walls
- rectifiedRotationMatrix = D:\projects\PassageFinder\PointCloudGeoregistration\data\processed\rectifiedRotationMatrix   # Folder for storing rectified rotation matrix
- clMLS = 95   # Confidence Level for MLS global accuracy
- eMLS = 1   # Known error of MLS global registration
- clCityGML = 90   # Confidence Level for CityGML global accuracy
- eCityGML = 0.04   # Known error of CityGML global registration
- tmpXYZbld = D:\projects\PassageFinder\PointCloudGeoregistration\data\processed\mlsToRANSAC   # Select tmp folder for partitioned MLS

Readers:
- CITYGML_1: CITYGML from $(SourceDataset_CITYGML)
- LAS_1: LAS from $(SourceDataset_LAS)
- LAS_2: LAS from $(SourceDataset_LAS_4)

Writers:
- LAS_3: LAS to $(DestDataset_LAS_2)

Note: General notes: / 1. The workflow operates on basis of selected building of interests (see the Decider transformer) / 2. The workspace integrates Python 3.7 scripts with libraries Open3D and Pyntcloud. Please check in advance whether this is compatible with your settings

Bookmark: 1.1 CityGML TUM campus
Note: epsg 31468
Address (reader CITYGML_1)
    attributes: citygml_target_uri xml_buffer, citygml_feature_role xml_buffer, citygml_feature_role_attr_name xml_buffer, citygml_feature_role_attr_val xml_buffer, gml_description xml_buffer, gml_name xml_buffer, citygml_address xml_xml
    -> Junction
Building (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer, citygml_storey_heights_above_ground_units xml_buffer,
      citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, DatenquelleBodenhoehe xml_buffer, DatenquelleDachhoehe xml_buffer, DatenquelleLage xml_buffer, GE_LoD2_zOffset xml_buffer, Gemeindeschluessel xml_buffer, HoeheDach xml_buffer, HoeheGrund xml_buffer, Methode xml_buffer, NiedrigsteTraufeDesGebaeudes xml_buffer, Qualitaet xml_buffer, StandLK xml_buffer
    -> Junction
CityModel (reader CITYGML_1)
    attributes: citygml_target_uri xml_buffer, gml_description xml_buffer, gml_name xml_buffer, citygml_city_object_member{}.xlink_href xml_buffer, gml_feature_member{}.xlink_href xml_buffer
GroundSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, Flaeche xml_buffer, Z_MAX xml_buffer, Z_MAX_ASL xml_buffer, Z_MIN xml_buffer, Z_MIN_ASL xml_buffer
    -> Junction
RoofSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, Dachneigung xml_buffer, Dachorientierung xml_buffer, Flaeche xml_buffer, Z_MAX xml_buffer, Z_MAX_ASL xml_buffer, Z_MIN xml_buffer, Z_MIN_ASL xml_buffer
    -> Junction
WallSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, Flaeche xml_buffer, Z_MAX xml_buffer, Z_MAX_ASL xml_buffer, Z_MIN xml_buffer, Z_MIN_ASL xml_buffer
    -> Junction
Junction
    -> Reprojector
Note: to ETRS89
Reprojector
    DEST = ETRS89.UTM-32N
    INTERPOLATION_TYPE_NAME = Nearest Neighbor
    RASTER_CELL_SIZE = Preserve Cells
    RASTER_TOLERANCE = 0.0
    SOURCE = Read from feature
    REPROJECTED -> Decider

Bookmark: 1 INPUT
Note: select building ID
Decider: TestFilter
    DEFAULT_VALUE = <UNFILTERED>
    TEST_LIST:
      "BOOL_OP,OR,COMPOSITE_TEST,""""""1 OR 2"""""",TEST_CLAUSE,TEST @Value(gml_id) = DEBY_LOD2_4959460
      TEST @Value(gml_parent_id) = DEBY_LOD2_4959460",DEBY_LOD2_4959460
    DEBY_LOD2_4959460 -> BoundsExtractor_2

Bookmark: 2.1 Confidence intervals estimation
BoundsExtractor_2
    ZMAX = maxHeight
    ZMIN = minHeight
    -> Split2parts
Split2parts: TestFilter
    DEFAULT_VALUE = <UNFILTERED>
    TEST_LIST = "BOOL_OP,OR,COMPOSITE_TEST,""""""1"""""",TEST_CLAUSE,TEST @Value(fme_feature_type) = GroundSurface",GroundSurface,"BOOL_OP,OR,COMPOSITE_TEST,""""""1"""""",TEST_CLAUSE,TEST @Value(fme_feature_type) = WallSurface",WallSurface,"BOOL_OP,OR,COMPOSITE_TEST,""""""1"""""",TEST_CLAUSE,TEST @Value(fme_feature_type) = Building",Building
    GroundSurface -> clCityGML
    WallSurface -> clMLS
    WallSurface -> clCityGML

Bookmark: 2.1.1.1 CL MLS
clMLS: TestFilter
    DEFAULT_VALUE = <UNFILTERED>
    TEST_LIST = "BOOL_OP,OR,COMPOSITE_TEST,""""""1"""""",TEST_CLAUSE,TEST $(clMLS) = 70",70,"BOOL_OP,OR,COMPOSITE_TEST,""""""1"""""",TEST_CLAUSE,TEST $(clMLS) = 75",75,"BOOL_OP,OR,COMPOSITE_TEST,""""""1"""""",TEST_CLAUSE,TEST $(clMLS) = 80",80,"BOOL_OP,OR,COMPOSITE_TEST,""""""1"""""",TEST_CLAUSE,TEST $(clMLS) = 85",85,"BOOL_OP,OR,COMPOSITE_TEST,""""""1"""""",TEST_CLAUSE,TEST $(clMLS) = 90",90,"BOOL_OP,OR,COMPOSITE_TEST,""""""1"""""",TEST_CLAUSE,TEST $(clMLS) = 92",92,"BOOL_OP,OR,COMPOSITE_TEST,""""""1"""""",TEST_CLAUSE,TEST $(clMLS) = 95",95,"BOOL_OP,OR,COMPOSITE_TEST,""""""1"""""",TEST_CLAUSE,TEST $(clMLS) = 96",96,"BOOL_OP,OR,COMPOSITE_TEST,""""""1"""""",TEST_CLAUSE,TEST $(clMLS) = 98",98,"BOOL_OP,OR,COMPOSITE_TEST,""""""1"""""",TEST_CLAUSE,TEST $(clMLS) = 99",99
    70 -> AttributeCreator
    75 -> AttributeCreator_2
    80 -> AttributeCreator_3
    85 -> AttributeCreator_4
    90 -> AttributeCreator_5
    92 -> AttributeCreator_7
    95 -> AttributeCreator_8
    96 -> AttributeCreator_9
    98 -> AttributeCreator_10
    99 -> AttributeCreator_11
AttributeCreator
    ATTR_TABLE = SET_TO clZ = 1.04
    -> Junction_5
AttributeCreator_2
    ATTR_TABLE = SET_TO clZ = 1.15
    -> Junction_5
AttributeCreator_3
    ATTR_TABLE = SET_TO clZ = 1.28
    -> Junction_5
AttributeCreator_4
    ATTR_TABLE = SET_TO clZ = 1.44
    -> Junction_5
AttributeCreator_5
    ATTR_TABLE = SET_TO clZ = 1.645
    -> Junction_5
AttributeCreator_7
    ATTR_TABLE = SET_TO clZ = 1.75
    -> Junction_5
AttributeCreator_8
    ATTR_TABLE = SET_TO clZ = 1.96
    -> Junction_5
AttributeCreator_9
    ATTR_TABLE = SET_TO clZ = 2.05
    -> Junction_5
AttributeCreator_10
    ATTR_TABLE = SET_TO clZ = 2.33
    -> Junction_5
AttributeCreator_11
    ATTR_TABLE = SET_TO clZ = 2.58
    -> Junction_5

Bookmark: 2.1.1 Calculations
Junction_5
    -> ExpressionEvaluator_2
Junction_6
    -> ExpressionEvaluator_4
FeatureMerger
    ATTR_ACCUM_MODE = Merge Supplier
    ATTR_CONFLICT_RES = Use Requestor
    IGNORE_NULLS = No
    JOIN_KEYS = @Value(gml_id) @Value(gml_id) AUTO
    MERGE_TYPE = Attributes Only
    PROCESS_DUPS = NO
    REJECT_NULL_MISSING_KEYS = No
    SUPPLIERS_FIRST = No
    MERGED -> ExpressionEvaluator_6
Note: calculate st dev
ExpressionEvaluator_6
    ACTION = Create New Attribute
    EXPRESSION = @sqrt(@sum(@pow(@Value(mlsStDev),2),@pow(@Value(citygmlStDev),2)))
    VAL_ATTR = stDev
    -> ExpressionEvaluator_8
Note: calculate interval
ExpressionEvaluator_8
    ACTION = Create New Attribute
    EXPRESSION = @mult(@Value(stDev),2)
    VAL_ATTR = intervalCL
    -> VariableSetter
Note: Error for each polygon is assumed to be Gaussian-like distributed and in L1 norm. / The final conf. value is set to 95% (1.96) / mu for the final interval is equal to position of the polygon in question
VariableSetter
    SCOPE = Global
    VALUE = @Value(intervalCL)
    VARNAME = inintCLglob
    -> Junction_8
BoundsExtractor_4
    ZMIN = groundSurfMin
    -> 2DForcer
2DForcer
    2D -> BuffererMinus
    2D -> Junction_2
Note: create inside buff to reject inside walls
BuffererMinus
    ANGLE = 22.5
    CAP_STYLE = Arc
    CORNER_STYLE = Arc
    MODE = AREA
    OFFSET = -0.1
    OFFSET_UNITS = NONE
    PRECISION = APPROX
    BUFFERED -> LineOnAreaOverlayer [AREA]
Note: Dissolver : Input
Junction_2
    -> Junction_10

Bookmark: 2.1.1.3 calculate mls st dev
Note: calculate mu
ExpressionEvaluator_2
    ACTION = Create New Attribute
    EXPRESSION = @div($(eMLS),2)
    VAL_ATTR = mlsMu
    -> ExpressionEvaluator_3
Note: calculate st dev
ExpressionEvaluator_3
    ACTION = Create New Attribute
    EXPRESSION = @div(@Value(mlsMu),@Value(clZ))
    VAL_ATTR = mlsStDev
    -> FeatureMerger [REQUESTOR]

Bookmark: 2.1.1.2 CL CityGML
clCityGML: TestFilter
    DEFAULT_VALUE = <UNFILTERED>
    TEST_LIST = "BOOL_OP,OR,COMPOSITE_TEST,""""""1"""""",TEST_CLAUSE,TEST $(clMLS) = 70",70,"BOOL_OP,OR,COMPOSITE_TEST,""""""1"""""",TEST_CLAUSE,TEST $(clMLS) = 75",75,"BOOL_OP,OR,COMPOSITE_TEST,""""""1"""""",TEST_CLAUSE,TEST $(clMLS) = 80",80,"BOOL_OP,OR,COMPOSITE_TEST,""""""1"""""",TEST_CLAUSE,TEST $(clMLS) = 85",85,"BOOL_OP,OR,COMPOSITE_TEST,""""""1"""""",TEST_CLAUSE,TEST $(clMLS) = 90",90,"BOOL_OP,OR,COMPOSITE_TEST,""""""1"""""",TEST_CLAUSE,TEST $(clMLS) = 92",92,"BOOL_OP,OR,COMPOSITE_TEST,""""""1"""""",TEST_CLAUSE,TEST $(clMLS) = 95",95,"BOOL_OP,OR,COMPOSITE_TEST,""""""1"""""",TEST_CLAUSE,TEST $(clMLS) = 96",96,"BOOL_OP,OR,COMPOSITE_TEST,""""""1"""""",TEST_CLAUSE,TEST $(clMLS) = 98",98,"BOOL_OP,OR,COMPOSITE_TEST,""""""1"""""",TEST_CLAUSE,TEST $(clMLS) = 99",99
    70 -> AttributeCreator_12
    75 -> AttributeCreator_13
    80 -> AttributeCreator_14
    85 -> AttributeCreator_15
    90 -> AttributeCreator_16
    92 -> AttributeCreator_17
    95 -> AttributeCreator_18
    96 -> AttributeCreator_19
    98 -> AttributeCreator_20
    99 -> AttributeCreator_21
AttributeCreator_12
    ATTR_TABLE = SET_TO clZ = 1.04
    -> Junction_6
AttributeCreator_13
    ATTR_TABLE = SET_TO clZ = 1.15
    -> Junction_6
AttributeCreator_14
    ATTR_TABLE = SET_TO clZ = 1.28
    -> Junction_6
AttributeCreator_15
    ATTR_TABLE = SET_TO clZ = 1.44
    -> Junction_6
AttributeCreator_16
    ATTR_TABLE = SET_TO clZ = 1.645
    -> Junction_6
AttributeCreator_17
    ATTR_TABLE = SET_TO clZ = 1.75
    -> Junction_6
AttributeCreator_18
    ATTR_TABLE = SET_TO clZ = 1.96
    -> Junction_6
AttributeCreator_19
    ATTR_TABLE = SET_TO clZ = 2.05
    -> Junction_6
AttributeCreator_20
    ATTR_TABLE = SET_TO clZ = 2.33
    -> Junction_6
AttributeCreator_21
    ATTR_TABLE = SET_TO clZ = 2.58
    -> Junction_6

Bookmark: 2.1.1.4 calculate CityGML st dev
Note: calculate mu
ExpressionEvaluator_4
    ACTION = Create New Attribute
    EXPRESSION = @div($(eCityGML),2)
    VAL_ATTR = citygmlMu
    -> ExpressionEvaluator_5
Note: calculate st dev
ExpressionEvaluator_5
    ACTION = Create New Attribute
    EXPRESSION = @div(@Value(citygmlMu),@Value(clZ))
    VAL_ATTR = citygmlStDev
    -> Split2parts_2
Split2parts_2: TestFilter
    DEFAULT_VALUE = <UNFILTERED>
    TEST_LIST = "BOOL_OP,OR,COMPOSITE_TEST,""""""1"""""",TEST_CLAUSE,TEST @Value(fme_feature_type) = GroundSurface",GroundSurface,"BOOL_OP,OR,COMPOSITE_TEST,""""""1"""""",TEST_CLAUSE,TEST @Value(fme_feature_type) = WallSurface",WallSurface
    GroundSurface -> BoundsExtractor_4
    WallSurface -> FeatureMerger [SUPPLIER]

Bookmark: 2.2 Evaluation of point cloud density per wall
Note: Calculate density of point cloud and check whether it covers walls
Junction_8
    -> GeometryExtractor
Note: MLS out with rectified height
Junction_3
    -> Junction_4

Bookmark: 2.2.1 Retrieve only walls
Note: extract geometry to assemble it further
GeometryExtractor
    ATTR = _geometry
    ELLIPSOID_NAME = WGS84
    GEOHASH_PRECISION_DISPLAY = ~9.3 mm (12 characters)
    ISO6709_FORMAT_CHOICE = Degrees and Decimal Degrees
    ISO6709_MAX_DECIMAL_PLACES = 5
    JSON_MAX_DIGITS = 7
    KIND_LONG = FME Binary
    LETTERING = WGS84
    LEVELS_ATTR = _levels
    MSSQL_FORMAT_CHOICE = Geometry
    OGCVERSION = 1.2
    OGC_WKT_PRECISION_DISPLAY = 64-bit
    OGEOSMS_URL_PREFIX = http://maps.google.com/?q=
    OMIT_NAMESPACES_DISPLAY = No
    PRECISION = 0
    PREFER_POLYGON_OVER_SURFACE = No
    REMOVE_GEOMETRY = No
    -> Counter_2
Note: wall id
Counter_2
    CNT_ATTR = wallID
    DOMAIN = @Value(gml_id)
    SCOPE = Local
    START = 1
    -> GeometryPartExtractor_4

Bookmark: extract lines creating walls
GeometryPartExtractor_4
    GQUERY:
      for $geom in //geometry
      where $geom/@fme_geometry_type = 'IFMELine'
      return number($geom/@fme_id)
    EXTRACTED -> Chopper_2
Note: select lowest line
Chopper_2
    DEAGGREGATE_INPUT = Deaggregate
    MAX_VERTICES = 2
    MODE = By Vertex
    REMNANT_ATTR = _remnant
    CHOPPED -> BoundsExtractor

Bookmark: 2.2.2 Split to lines and select lowest line
BoundsExtractor
    ZMAX = LineH
    -> TestFilter_4
TestFilter_4
    DEFAULT_VALUE = <UNFILTERED>
    TEST_LIST:
      "BOOL_OP,AND,COMPOSITE_TEST,""""""1 AND 2"""""",TEST_CLAUSE,TEST @Value(LineH) >= @sub(@Value(minHeight),0.5)
      TEST @Value(LineH) <= @sum(@Value(minHeight),0.5)",lowestLine
    lowestLine -> StringConcatenator_4
Note: create unique id for wall
StringConcatenator_4
    ACTION = Create New Attribute
    PARM_LINE = fme_basicstring:14%1%14:@Value(gml_id)_@Value(wallID)
    VAL_ATTR = wallUniID
    -> LineOnAreaOverlayer [LINE]
Note: check walls inside bld
LineOnAreaOverlayer
    CLEANING_TOLERANCE = Automatic
    DEAGGREGATE_INPUT = Yes
    OV_ATTR = _inside
    LINE -> Tester
Note: reject walls inside bld
Tester
    BOOL_OP = OR
    COMPOSITE_TEST = 1
    TEST_CLAUSE = TEST @Value(_inside) = 0
    TEST_MODE = TEST
    PASSED -> ExpressionEvaluator_9

Bookmark: 2.2.3 Calculate the line H for CL interval
ExpressionEvaluator_9
    ACTION = Create New Attribute
    EXPRESSION = @sub(@Value(minHeight),@Value(intervalCL))
    VAL_ATTR = maxMinH
    -> 2DForcer_2
2DForcer_2
    2D -> GeometryValidator
Note: check duplicate points
GeometryValidator
    ISSUE_ATTR_NAME = _issues
    PRESETS = Custom
    REPAIR = No
    RULES = CONSECUTIVE_IDENTICAL_VERTICES_2D CHECK_Z]YES]TOLERANCE]0.0]FME_CONTROLLER_QUERY_FILE]transformers/dependencies/geometryvalidator/CONSECUTIVE_IDENTICAL_VERTICES_2D.fme
    SUMMARY = Detailed
    PASSED -> LineExtender

Bookmark: 2.3.4: Create rectangular buffer - offset
Note: rectanguilar buffer as L1 norm
Note: L1 norm, extend line for each end by: / interval/2
LineExtender
    LEN = @div(@Value(intervalCL),2)
    STRETCHED -> COUNTER1
    STRETCHED -> COUNTER2
    STRETCHED -> COUNTER3
    STRETCHED -> COUNTER1_2
    STRETCHED -> COUNTER2_2
    STRETCHED -> COUNTER3_2

Bookmark: one side buffer - left
COUNTER1: Counter
    CNT_ATTR = count
    DOMAIN = counter1
    SCOPE = Global
    START = 0
    -> BUFFERER_4
Note: Buffer the side you DON'T want!
BUFFERER_4: Bufferer
    ANGLE = 22.5
    BUFFSTYLE = RIGHT_SIDE_ONLY
    WIDTH = @Value(intervalCL)
    BUFFERED -> COMMONSEGMENTFINDER [BASE]
COUNTER2: Counter
    CNT_ATTR = count
    DOMAIN = counter2
    SCOPE = Global
    START = 0
    -> BUFFERER_6
Note: A butt buffer
BUFFERER_6: Bufferer
    ANGLE = 22.5
    BUFFSTYLE = CAP_BUTT
    WIDTH = @Value(intervalCL)
    BUFFERED -> INTERSECTOR
COUNTER3: Counter
    CNT_ATTR = count
    DOMAIN = counter3
    SCOPE = Global
    START = 0
    -> INTERSECTOR
Note: Intersect buffer and line to / split buffer into left-right sides
INTERSECTOR: Intersector
    DUPLICATE_Z_NODES = No
    GRP_BY = count
    OV_ATTR = overlaps
    SEG_ATTR = _segments
    INTERSECTED -> COMMONSEGMENTFINDER [CANDIDATE]
Note: Throw away the part of the buffer / that matches the side you don't want.
COMMONSEGMENTFINDER: CommonSegmentFinder
    GROUP_BY = count
    NO_OVERLAP -> AreaBuilder_2
AreaBuilder_2
    ALLOW_CYCLES = No
    CHECK_CURVE_DIRECTION = No
    CONNECT_Z_MODE = First Wins
    CONSIDER_NODE_ELEVATION = no
    DEAGGREGATE_INPUT = Deaggregate
    DONUT_CREATION = NO
    GROUP_BY = count
    LINES_AS_SEGMENTS = No
    POLY_ACCUM_ATTRS_NAME = Use Attributes From One Feature
    SNAPTYPE_PARAM = None
    AREA -> Dissolver_4

Bookmark: one side buffer - right
COUNTER1_2: Counter
    CNT_ATTR = count
    DOMAIN = counter1
    SCOPE = Global
    START = 0
    -> BUFFERER_2
Note: Buffer the side you DON'T want!
BUFFERER_2: Bufferer
    ANGLE = 22.5
    BUFFSTYLE = LEFT_SIDE_ONLY
    WIDTH = @Value(intervalCL)
    BUFFERED -> COMMONSEGMENTFINDER_2 [BASE]
COUNTER2_2: Counter
    CNT_ATTR = count
    DOMAIN = counter2
    SCOPE = Global
    START = 0
    -> BUFFERER_3
Note: A butt buffer
BUFFERER_3: Bufferer
    ANGLE = 22.5
    BUFFSTYLE = CAP_BUTT
    WIDTH = @Value(intervalCL)
    BUFFERED -> INTERSECTOR_2
COUNTER3_2: Counter
    CNT_ATTR = count
    DOMAIN = counter3
    SCOPE = Global
    START = 0
    -> INTERSECTOR_2
Note: Intersect buffer and line to / split buffer into left-right sides
INTERSECTOR_2: Intersector
    DUPLICATE_Z_NODES = No
    GRP_BY = count
    OV_ATTR = overlaps
    SEG_ATTR = _segments
    INTERSECTED -> COMMONSEGMENTFINDER_2 [CANDIDATE]
Note: Throw away the part of the buffer / that matches the side you don't want.
COMMONSEGMENTFINDER_2: CommonSegmentFinder
    GROUP_BY = count
    NO_OVERLAP -> AreaBuilder
AreaBuilder
    ALLOW_CYCLES = No
    CHECK_CURVE_DIRECTION = No
    CONNECT_Z_MODE = First Wins
    CONSIDER_NODE_ELEVATION = no
    DEAGGREGATE_INPUT = Deaggregate
    DONUT_CREATION = NO
    GROUP_BY = count
    LINES_AS_SEGMENTS = No
    POLY_ACCUM_ATTRS_NAME = Use Attributes From One Feature
    SNAPTYPE_PARAM = None
    AREA -> Dissolver_4

Bookmark: 2.3.5 Discretization of intervals
Note: merge both sides, extruders for L1 norm
Dissolver_4
    ACCUM_INPUT_ATTRS = Use Attributes From One Feature
    CLEANING_TOLERANCE = Automatic
    CONNECT_Z_MODE = First Wins
    DEAGGREGATE_INPUT = Yes
    GROUP_BY = wallUniID
    AREA -> 3DForcer
    AREA -> Dissolver
3DForcer
    KEEPZVAL = No
    ZVALATTR = @Value(maxMinH)
    -> ExpressionEvaluator_7
ExpressionEvaluator_7
    ACTION = Create New Attribute
    EXPRESSION = @sum(@mult(@Value(intervalCL),2),@sub(@Value(maxHeight),@Value(minHeight)))
    VAL_ATTR = hExtrusion
    -> Extruder
Note: finalize 3D boxes within introduced confidence intervals
Extruder
    DIRECTION = Vertical
    DISTANCE = @Value(hExtrusion)
    EXTRUDED -> VolumeCalculator

Bookmark: 2.3.7 Density threshold
Note: calc. volume of 3D boxes to introduce continuity measure (next section)
VolumeCalculator
    MULT = 1
    SET_TRAIT = No
    VOLUME_ATTR = vol3Dboxes
    -> Clipper_2 [CLIPPER]
    -> FeatureMerger_6 [REQUESTOR]
Clipper_2
    ATTR_ACCUM_MODE = Merge Clipper
    ATTR_CONFLICT_RES = Use Clipper
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> PointCloudPropertyExtractor_2
Note: count nr of points within a box
PointCloudPropertyExtractor_2
    CALCULATE_EXTENTS_DISPLAY = No
    POINT_COMPONENTS = "x    y    z   "
    -> tmpIDgroup
tmpIDgroup: AttributeCreator
    ATTR_TABLE = SET_TO groupingTmp = 1
    -> PercentileCalculator
Note: pass above the value of 60th percentile
PercentileCalculator
    attribute_perc = _num_points
    group_attr = groupingTmp
    lower_percentile = 5
    upper_percentile = 60
    Top_cut-off -> BoundsExtractor_10
    Top_cut-off -> FeatureMerger_4 [REQUESTOR]

Bookmark: 2.3.6 Dissolve ground surface with L1 norm bounds
Note: GroundSurface
Junction_10
    -> Dissolver
Dissolver
    ACCUM_INPUT_ATTRS = Use Attributes From One Feature
    CLEANING_TOLERANCE = Automatic
    CONNECT_Z_MODE = First Wins
    DEAGGREGATE_INPUT = Yes
    AREA -> Clipper_3 [CLIPPER]
Clipper_3
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> PointCloudCombiner_3
Junction_18
    -> Junction_3
    -> Clipper_2 [CLIPPEE]

Bookmark: 1.2 Point clouds, whole
Note: laser1
Note: laser1
LAS (reader LAS_1)
    -> CoordinateSystemSetter
Note: laser2
LAS (reader LAS_2)
    -> CoordinateSystemSetter
Note: ETRS89
CoordinateSystemSetter
    COORDSYS = ETRS89.UTM-32N
    -> tmpId_2
    -> BoundingBoxReplacer_3

Bookmark: 2.1.2 Global center of scene extractor
tmpId_2: AttributeCreator
    ATTR_TABLE = SET_TO tmpBBID = 1
    -> FeatureMerger_5 [REQUESTOR]
BoundingBoxReplacer_3
    BOXTYPE = 3D Bounding Cube
    BOX -> Aggregator
Aggregator
    ACCUM_ATTRS_NAME = Use Attributes From One Feature
    AGGREGATE_TYPE = Homogeneous Collection (If Possible)
    ATTR_TO_TRAIT = Yes
    ID_SELECTION = ID and Parent ID
    MODE = Geometry - Assemble One Level
    PRESERVE_ID = No
    SEP = ,
    AGGREGATE -> CenterPointExtractor
CenterPointExtractor
    CENTX = centX
    CENTY = centY
    EXTRACTIONMODE = CENTER
    -> BoundsExtractor_3
BoundsExtractor_3
    ZMIN = minPclZ
    -> ExpressionEvaluator_10
ExpressionEvaluator_10
    ACTION = Create New Attribute
    EXPRESSION = @sub(@Value(minPclZ),1)
    VAL_ATTR = centMinZ
    -> tmpId
tmpId: AttributeCreator
    ATTR_TABLE = SET_TO tmpBBID = 1
    -> FeatureMerger_5 [SUPPLIER]
FeatureMerger_5
    ATTR_ACCUM_MODE = Merge Supplier
    ATTR_CONFLICT_RES = Use Requestor
    IGNORE_NULLS = No
    JOIN_KEYS = @Value(tmpBBID) @Value(tmpBBID) AUTO
    MERGE_TYPE = Attributes Only
    PROCESS_DUPS = NO
    REJECT_NULL_MISSING_KEYS = No
    SUPPLIERS_FIRST = No
    MERGED -> Tiler_2
Note: for processing boost
Tiler_2
    BOUNDARY_CASES = No
    CLEANING_TOLERANCE = Automatic
    COL_ATTR = _column
    LINES_AS_SEGMENTS = No
    MEASURE_TYPE = Continuous
    MISSING_VAL_MODE = Compute
    NUM_HORIZONTAL_TILES = 10
    NUM_VERTICAL_TILES = 10
    ROW_ATTR = _row
    STARTINGCORNER = Lower Left
    TILING_TYPE = Number of Tiles
    TILED -> Clipper_3 [CLIPPEE]

Bookmark: caluclate ground height of MLS
Note: point clouds within accuracy to rectified matrix
PointCloudCombiner_3
    ACCUM_ATTRS_NAME = Yes
    EXTRACT_RASTER_NODATA_NAME = No
    GROUP_BY = gml_id
    SPACING = 1.0
    -> tmpIDgroup_2
    -> FeatureMerger_2 [REQUESTOR]
tmpIDgroup_2: AttributeCreator
    ATTR_TABLE = SET_TO gTmp = 1
    -> PointCloudThinner_2
PointCloudThinner_2
    INTERVAL = 10000
    THINNED -> PointCloudCoercer_2
PointCloudCoercer_2
    ACCUM_ATTRS_NAME = Yes
    CONVERT_TO_DISPLAY = Individual Points
    PART_NUMBER_ATTR_NAME = _part_number
    POINT_COMPONENTS_PRESERVE_DISPLAY = Attributes
    COERCED -> BoundsExtractor_6
BoundsExtractor_6
    ZMAX = z
    -> PercentileCalculator_2
Note: pass below 5th perc of height
PercentileCalculator_2
    attribute_perc = z
    group_attr = gTmp
    lower_percentile = 5
    upper_percentile = 60
    Bottom_cut-off -> PointCloudCombiner_4
PointCloudCombiner_4
    ACCUM_ATTRS_NAME = Yes
    EXTRACT_RASTER_NODATA_NAME = No
    SPACING = 1.0
    -> PointCloudStatisticsCalculator
PointCloudStatisticsCalculator
    POINT_COMPONENTS = "z        MODE intensity        "
    -> AttributeRenamer
AttributeRenamer
    ATTR_TABLE = RENAME_SET_DEFAULT z.mode > groundSurfPclMin
    -> FeatureMerger_2 [SUPPLIER]
FeatureMerger_2
    ATTR_ACCUM_MODE = Merge Supplier
    ATTR_CONFLICT_RES = Use Requestor
    IGNORE_NULLS = No
    JOIN_KEYS = @Value(gml_id) @Value(gml_id) AUTO
    MERGE_TYPE = Attributes Only
    PROCESS_DUPS = NO
    REJECT_NULL_MISSING_KEYS = No
    SUPPLIERS_FIRST = No
    MERGED -> ExpressionEvaluator
ExpressionEvaluator
    ACTION = Create New Attribute
    EXPRESSION = @sub(@Value(groundSurfMin),@Value(groundSurfPclMin))
    VAL_ATTR = heightInit
    -> Offsetter_8
Offsetter_8
    MODE = Cartesian Coordinate
    XOFF = 0
    YOFF = 0
    ZOFF = @Value(heightInit)
    OFFSET -> Junction_18

Bookmark: 3D oriented BBox
BoundsExtractor_10
    ZMAX = _zmax
    ZMIN = _zmin
    -> PointCloudCoercer
PointCloudCoercer
    ACCUM_ATTRS_NAME = Yes
    CONVERT_TO_DISPLAY = Single Multipoint
    PART_NUMBER_ATTR_NAME = _part_number
    COERCED -> BoundingBoxReplacer_2
BoundingBoxReplacer_2
    BOXTYPE = 2D Oriented Bounding Box
    BOX -> 3DForcer_2
3DForcer_2
    KEEPZVAL = No
    ZVALATTR = @Value(_zmin)
    -> Extruder_2
Extruder_2
    DIRECTION = Auto
    DISTANCE = @sub(@Value(_zmax),@Value(_zmin))
    EXTRUDED -> VolumeCalculator_2

Bookmark: ratio threshold
Note: Calc. volume of occupation space for 3D point clouds
VolumeCalculator_2
    MULT = 1
    SET_TRAIT = No
    VOLUME_ATTR = volPCL
    -> ratioCalc
ratioCalc: ExpressionEvaluator
    ACTION = Create New Attribute
    EXPRESSION = @div(@Value(volPCL),@Value(vol3Dboxes))
    VAL_ATTR = ratio
    -> Tester_2
Note: threshold ratio >0.6
Tester_2
    BOOL_OP = OR
    COMPOSITE_TEST = 1
    TEST_CLAUSE = NUM_TEST @Value(ratio) > 0.6
    TEST_MODE = TEST
    PASSED -> FeatureMerger_4 [SUPPLIER]

Bookmark: 2.3.8 continuity threshold
FeatureMerger_4
    ATTR_ACCUM_MODE = Merge Supplier
    ATTR_CONFLICT_RES = Use Requestor
    IGNORE_NULLS = No
    JOIN_KEYS = @Value(gml_id) @Value(gml_id) AUTO
    MERGE_TYPE = Attributes Only
    PROCESS_DUPS = NO
    REJECT_NULL_MISSING_KEYS = No
    SUPPLIERS_FIRST = No
    MERGED -> FeatureMerger_6 [SUPPLIER]
    MERGED -> PointCloudCombiner_6

Bookmark: 2.4 Space occupation
Note: pass only adequately covered 3D boxes
FeatureMerger_6
    ATTR_ACCUM_MODE = Merge Supplier
    ATTR_CONFLICT_RES = Use Requestor
    IGNORE_NULLS = No
    JOIN_KEYS = @Value(gml_id) @Value(gml_id) AUTO
    MERGE_TYPE = Attributes Only
    PROCESS_DUPS = NO
    REJECT_NULL_MISSING_KEYS = No
    SUPPLIERS_FIRST = No
    MERGED -> GeometryReplacer
    MERGED -> BoundsExtractor_7
    MERGED -> 2DForcer_4
Note: point id
PointCloudCombiner_6
    ACCUM_ATTRS_NAME = Yes
    EXTRACT_RASTER_NODATA_NAME = No
    SPACING = 1.0
    -> Clipper_4 [CLIPPEE]

Bookmark: 2.5.1 partition mls per each citygml wall segment
2DForcer_4
    2D -> Deaggregator_2
Deaggregator_2
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = Yes
    DEAGGREGATED -> GeometryFilter_2
GeometryFilter_2
    BREAK_AGG = No
    GEOM_PORT_NAMES = Area Surface
    AREA -> DuplicateFilter
    SURFACE -> DuplicateFilter
Note: double-check
DuplicateFilter
    INPUT_ORDERED_CHOICE = No
    KEYATTR = wallUniID
    UNIQUE -> Junction_7

Bookmark: 2.5 Normalize point cloud
Junction_7
    -> Clipper_6 [CLIPPER]
Note: PointCloudCombiner_5 : Input
Junction_9
    -> Junction_11
Note: FeatureMerger_7 : Merged
Junction_11
    -> PointCloudCombiner_5
PointCloudCombiner_5
    ACCUM_ATTRS_NAME = Yes
    EXTRACT_RASTER_NODATA_NAME = No
    GROUP_BY = gml_parent_id
    SPACING = 1.0
    -> Offsetter_6
Note: offset to the centre of the scene
Offsetter_6
    MODE = Cartesian Coordinate
    XOFF = -@Value(centX)
    YOFF = -@Value(centY)
    ZOFF = -@Value(centMinZ)
    OFFSET -> CoordinateSystemRemover_2
CoordinateSystemRemover_2
    -> AttributeCleaner
PointCloudCombiner
    ACCUM_ATTRS_NAME = Yes
    EXTRACT_RASTER_NODATA_NAME = No
    GROUP_BY = gml_parent_id
    SPACING = 1.0
    -> Clipper_6 [CLIPPEE]
Note: partition to single walls for RANSAC
Clipper_6
    ATTR_ACCUM_MODE = Merge Clipper
    ATTR_CONFLICT_RES = Use Clipper
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> Offsetter_3
Note: offset to the centre of the scene
Offsetter_3
    MODE = Cartesian Coordinate
    XOFF = -@Value(centX)
    YOFF = -@Value(centY)
    ZOFF = -@Value(centMinZ)
    OFFSET -> CoordinateSystemRemover
CoordinateSystemRemover
    -> AttributeCleaner_2

Bookmark: 2.4.1 Dissolve 3D boxes
BoundsExtractor_7
    ZMAX = maxMaxH
    -> 2DForcer_3
2DForcer_3
    2D -> Deaggregator
Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = Yes
    DEAGGREGATED -> GeometryFilter
GeometryFilter
    BREAK_AGG = No
    GEOM_PORT_NAMES = Area Surface
    AREA -> Dissolver_2
    SURFACE -> Dissolver_2
Dissolver_2
    ACCUM_INPUT_ATTRS = Use Attributes From One Feature
    CLEANING_TOLERANCE = Automatic
    CONNECT_Z_MODE = First Wins
    DEAGGREGATE_INPUT = Yes
    AREA -> 3DForcer_4
3DForcer_4
    KEEPZVAL = No
    ZVALATTR = @Value(maxMinH)
    -> Extruder_4
Extruder_4
    DIRECTION = Auto
    DISTANCE = @sub(@Value(maxMaxH),@Value(maxMinH))
    EXTRUDED -> 3DBoxSampler

Bookmark: 2.4.2 partition 3D boxes to 3D grid
3DBoxSampler: PointCloudCombiner
    ACCUM_ATTRS_NAME = Yes
    EXTRACT_RASTER_NODATA_NAME = No
    SPACING = 2
    -> PointCloudCoercer_3
PointCloudCoercer_3
    ACCUM_ATTRS_NAME = Yes
    CONVERT_TO_DISPLAY = Individual Points
    PART_NUMBER_ATTR_NAME = _part_number
    POINT_COMPONENTS_PRESERVE_DISPLAY = Attributes
    COERCED -> Counter
Counter
    CNT_ATTR = _count
    DOMAIN = counter
    SCOPE = Local
    START = 0
    -> Bufferer
Bufferer
    MODE = SOLID
    OFFSET = 1
    SPHERE_DIVISIONS = 2
    BUFFERED -> BoundsExtractor_5
BoundsExtractor_5
    ZMIN = small3DBoxmin
    -> BoundingBoxReplacer
Note: create manhattan-like face
BoundingBoxReplacer
    BOXTYPE = 2D Oriented Bounding Box
    BOX -> 3DForcer_3
3DForcer_3
    KEEPZVAL = No
    ZVALATTR = @Value(small3DBoxmin)
    -> Extruder_3
Extruder_3
    DIRECTION = Auto
    DISTANCE = 2
    EXTRUDED -> 3dgridId
3dgridId: Counter
    CNT_ATTR = 3dgridId
    DOMAIN = counter
    SCOPE = Local
    START = 0
    -> Clipper [CLIPPER]
    -> Clipper_4 [CLIPPER]

Bookmark: 2.4.3 Sample covered walls into point clouds
Note: retrieve raw geometry of walls
GeometryReplacer
    ELLIPSOID_NAME = WGS84
    KIND_LONG = FME Binary
    LETTERING = WGS84
    MSSQL_FORMAT_CHOICE = Geometry
    OGC_WKT_PRECISION_DISPLAY = 64-bit
    OUTPUT_POINT_DISPLAY = Point
    REMOVE_ATTRIBUTE = Yes
    SOURCE = @Value(_geometry)
    SRS_AXIS_ORDER_DISPLAY = Automatic
    -> CityGMLSampler
CityGMLSampler: PointCloudCombiner
    ACCUM_ATTRS_NAME = Yes
    EXTRACT_RASTER_NODATA_NAME = No
    GROUP_BY = gml_id
    SPACING = 0.1
    -> PointCloudCombiner_2
PointCloudCombiner_2
    ACCUM_ATTRS_NAME = Yes
    EXTRACT_RASTER_NODATA_NAME = No
    SPACING = 1.0
    -> Clipper [CLIPPEE]

Bookmark: 2.4.4 Occupation for CityGML features
Clipper
    ATTR_ACCUM_MODE = Merge Clipper
    ATTR_CONFLICT_RES = Use Clippee
    BOUNDARY_CASES = Treat as Inside
    CLEANING_TOLERANCE = Automatic
    CLIPPED_ATTR = occupied
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> Tester_3
Note: pass only occupied
Tester_3
    BOOL_OP = OR
    COMPOSITE_TEST = 1
    TEST_CLAUSE = TEST @Value(occupied) = yes
    TEST_MODE = TEST
    PASSED -> AttributeKeeper_2
AttributeKeeper_2
    CREATE_BULK_MODE_FEATURES = NO
    KEEP_ATTRS = 3dgridId,gml_id,gml_parent_id,centMinZ,centX,centY
    -> FeatureMerger_8 [SUPPLIER]
    -> FeatureMerger_7 [REQUESTOR]
FeatureMerger_7
    ATTR_ACCUM_MODE = Merge Supplier
    ATTR_CONFLICT_RES = Use Requestor
    IGNORE_NULLS = No
    JOIN_KEYS = @Value(3dgridId) @Value(3dgridId) AUTO
    MERGE_TYPE = Attributes Only
    PROCESS_DUPS = NO
    REJECT_NULL_MISSING_KEYS = No
    SUPPLIERS_FIRST = No
    MERGED -> Junction_9

Bookmark: 2.4.5 Occupation for MLS features
Clipper_4
    ATTR_ACCUM_MODE = Merge Clipper
    ATTR_CONFLICT_RES = Use Clippee
    BOUNDARY_CASES = Treat as Inside
    CLEANING_TOLERANCE = Automatic
    CLIPPED_ATTR = occupied
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> Tester_4
Note: pass only occupied
Tester_4
    BOOL_OP = OR
    COMPOSITE_TEST = 1
    TEST_CLAUSE = TEST @Value(occupied) = yes
    TEST_MODE = TEST
    PASSED -> AttributeKeeper
AttributeKeeper
    CREATE_BULK_MODE_FEATURES = NO
    KEEP_ATTRS = 3dgridId,gml_id,gml_parent_id,centMinZ,centX,centY
    -> FeatureMerger_8 [REQUESTOR]
    -> FeatureMerger_7 [SUPPLIER]
FeatureMerger_8
    ATTR_ACCUM_MODE = Merge Supplier
    ATTR_CONFLICT_RES = Use Requestor
    IGNORE_NULLS = No
    JOIN_KEYS = @Value(3dgridId) @Value(3dgridId) AUTO
    MERGE_TYPE = Attributes Only
    PROCESS_DUPS = NO
    REJECT_NULL_MISSING_KEYS = No
    SUPPLIERS_FIRST = No
    MERGED -> PointCloudCombiner

Bookmark: AttributeCleaner
AttributeCleaner: AttributeKeeper
    CREATE_BULK_MODE_FEATURES = NO
    KEEP_ATTRS = gml_parent_id
    -> FeatureWriter [File1]
AttributeCleaner_2: AttributeKeeper
    CREATE_BULK_MODE_FEATURES = NO
    KEEP_ATTRS = gml_parent_id,wallUniID
    -> FeatureWriter_3 [Output]

Bookmark: 2.7 ICP (open3D) integration
Note: save as tmp XYZ point cloud
FeatureWriter
    DATASET = $(CityModelForReference)
    DATASET_ATTR = _dataset
    FEATURE_TYPE_LIST_ATTR = _feature_type
    FORMAT = POINTCLOUDXYZ
    POINTCLOUDXYZ_APPEND = No
    POINTCLOUDXYZ_COLUMN_TO_PCCOMPONENT = x,x,y,y,z,z
    POINTCLOUDXYZ_COORDINATE_SYSTEM_GRANULARITY = FEATURE
    POINTCLOUDXYZ_DESTINATION_DATASETTYPE_VALIDATION = Yes
    POINTCLOUDXYZ_ENCODING = UTF-8
    POINTCLOUDXYZ_EXTENSION = xyz
    POINTCLOUDXYZ_INCLUDE_FIELD_NAME = yes
    POINTCLOUDXYZ_QUOTE_FIELD_NAMES = if_needed
    POINTCLOUDXYZ_QUOTE_OUTPUT = if_needed
    POINTCLOUDXYZ_SEPARATOR = space
    POINTCLOUDXYZ_WRITE_UTF8_BOM = yes
    TOTAL_FEATURES_WRITTEN_ATTR = _total_features_written
    SUMMARY -> FeatureHolder
Note: save as tmp XYZ point cloud
FeatureWriter_2
    DATASET = $(MLSforRegistration)
    DATASET_ATTR = _dataset
    FEATURE_TYPE_LIST_ATTR = _feature_type
    FORMAT = POINTCLOUDXYZ
    POINTCLOUDXYZ_APPEND = No
    POINTCLOUDXYZ_COLUMN_TO_PCCOMPONENT = x,x,y,y,z,z
    POINTCLOUDXYZ_COORDINATE_SYSTEM_GRANULARITY = FEATURE
    POINTCLOUDXYZ_DESTINATION_DATASETTYPE_VALIDATION = Yes
    POINTCLOUDXYZ_ENCODING = UTF-8
    POINTCLOUDXYZ_EXTENSION = xyz
    POINTCLOUDXYZ_INCLUDE_FIELD_NAME = yes
    POINTCLOUDXYZ_QUOTE_FIELD_NAMES = if_needed
    POINTCLOUDXYZ_QUOTE_OUTPUT = if_needed
    POINTCLOUDXYZ_SEPARATOR = space
    POINTCLOUDXYZ_WRITE_UTF8_BOM = yes
    TOTAL_FEATURES_WRITTEN_ATTR = _total_features_written
    SUMMARY -> GeometryRemover
FeatureHolder
    -> Tester_5
Note: trick for sequence
Tester_5
    BOOL_OP = OR
    COMPOSITE_TEST = 1
    TEST_CLAUSE = TEST @Value(del) != 1
    TEST_MODE = TEST
    PASSED -> VariableRetriever
VariableRetriever
    SCOPE = Global
    VALUE_ATTR = intervalCL
    VARNAME = inintCLglob
    -> PythonModuleInstaller
Note: install open3D library
PythonModuleInstaller
    PYTHON_MODULES = open3d
    TRY_IMPORT = No
    -> PythonCaller
Note: ICP Open3D call
PythonCaller
    PYTHONSOURCE:
      import fme
      from fmeobjects import (FMELogFile,
                              FME_WARN)#FME native logs
      # import algorithm-specific libraries
      import os
      import numpy as np
      import open3d as o3d

      ## GLOBALS

      #read user selected paths as string
      cityGmlPath = str(FME_MacroValues['CityModelForReference'] + '\\')
      mlsPath = str(FME_MacroValues['MLSforRegistration'] + '\\')
      rectifRotMatrix = str(FME_MacroValues['rectifiedRotationMatrix'] + '\\')

      #list of full paths of point cloud subsets
      cityGmlIds=[]
      for root, dirs, files in os.walk(cityGmlPath):
          for fname in files:
              cityGmlIds.append(os.path.join(root, fname))


      mlsIds = []
      for root, dirs, files in os.walk(mlsPath):
          for fname in files:
              mlsIds.append(os.path.join(root, fname))



      #list of xyz file names (should be same for CityGML and MLS point clouds)
      gmlParentIds = os.listdir(cityGmlPath)
      mlsParentIds = os.listdir(mlsPath)

      #index for iteration
      index = len(gmlParentIds)


      def icp(feature):
          for i in range (index):
              FMELogFile().logMessageString("#--- The ICP Point-2-Plane algorithm has been triggered... ---#", FME_WARN)
              ### MLS ###
              ##Read the mls point cloud

              FMELogFile().logMessageString("#--- MLS point cloud loading...", FME_WARN)
              mls = o3d.io.read_point_cloud(mlsIds[i])
              #mls = o3d.io.read_point_cloud("D:/projects/PassageFinder/PointCloudGeoregistration/data/processed/mlsToBeRegistered/mlsToBeRegistered.xyz")


              #FMELogFile().logMessageString("#--- Downsample the point cloud with a voxel of 0.1m...", FME_WARN)
              downMls = mls.voxel_down_sample(voxel_size=0.1)


              #FMELogFile().logMessageString("#--- Recompute the normal of the downsampled point cloud, radius 1, maxnn 100...", FME_WARN)
              downMls.estimate_normals(search_param=o3d.geometry.KDTreeSearchParamHybrid(radius=1, max_nn=100))

              ### CityGML ###
              ##Read the city gml sampled point cloud (0.1 m sample)
              FMELogFile().logMessageString("#--- CityGML sampled point cloud loading...", FME_WARN)
              citygml = o3d.io.read_point_cloud(cityGmlIds[i])
              #citygml = o3d.io.read_point_cloud("D:/projects/PassageFinder/PointCloudGeoregistration/data/processed/citygmlToBeReferenced/citygmlToBeReferenced.xyz")


              #print("Downsample the point cloud with a voxel of 0.1m")
              downCitygml = citygml.voxel_down_sample(voxel_size=0.1)


              #print("Recompute the normal of the downsampled point cloud, radius 1, maxnn 100")
              downCitygml.estimate_normals(search_param=o3d.geometry.KDTreeSearchParamHybrid(radius=1, max_nn=100))


              ### Registration ###
              #more here:
              #http://www.open3d.org/docs/latest/tutorial/Basic/icp_registration.html


              #print("Registration, with threshold 1m, and init not-altering-affine-matrix")
              threshold = float(feature.getAttribute('intervalCL')) #float -> to ensure numbers' parsing

              #init 3d affine matrix with no transformation as point clouds are already aligned
              trans_init = np.asarray([[1.0, 0.0, 0.0, 0.0],
                                        [0.0, 1.0, 0.0, 0.0],
                                        [0.0, 0.0, 1.0, 0.0],
                                        [0.0, 0.0, 0.0, 1.0]])


              #apply point-2-plane ICP
              FMELogFile().logMessageString("#--- Apply point-to-plane ICP...", FME_WARN)
              reg_p2l = o3d.pipelines.registration.registration_icp(
                  downMls, downCitygml, threshold, trans_init,
                  o3d.pipelines.registration.TransformationEstimationPointToPlane())

              #write out the correct transformation matrix to apply it in the FME...
              affineMatrix = reg_p2l.transformation
              csvPath = rectifRotMatrix + gmlParentIds[i].strip('.xyz') + ".csv"

              np.savetxt(csvPath, affineMatrix, delimiter=",")
    PYTHONSYMBOL = icp
    -> ListExploder_2

Bookmark: 2.6.1 Intermediate writer Bld RANSAC
Note: xyz
FeatureWriter_3
    DATASET = $(tmpXYZbld)
    DATASET_ATTR = _dataset
    FEATURE_TYPE_LIST_ATTR = _feature_type
    FORMAT = POINTCLOUDXYZ
    POINTCLOUDXYZ_APPEND = No
    POINTCLOUDXYZ_COLUMN_TO_PCCOMPONENT = x,x,y,y,z,z
    POINTCLOUDXYZ_COORDINATE_SYSTEM_GRANULARITY = FEATURE
    POINTCLOUDXYZ_DESTINATION_DATASETTYPE_VALIDATION = Yes
    POINTCLOUDXYZ_ENCODING = UTF-8
    POINTCLOUDXYZ_EXTENSION = xyz
    POINTCLOUDXYZ_INCLUDE_FIELD_NAME = yes
    POINTCLOUDXYZ_QUOTE_FIELD_NAMES = if_needed
    POINTCLOUDXYZ_QUOTE_OUTPUT = if_needed
    POINTCLOUDXYZ_SEPARATOR = ;
    POINTCLOUDXYZ_WRITE_UTF8_BOM = yes
    TOTAL_FEATURES_WRITTEN_ATTR = _total_features_written
    SUMMARY -> PythonModuleInstaller_2

Bookmark: 2.6: RANSAC (pyntcloud) integration
Note: install pyntcloud library
PythonModuleInstaller_2
    PYTHON_MODULES = pyntcloud
    TRY_IMPORT = No
    -> PythonCaller_2
Note: RANSAC call
PythonCaller_2
    PYTHONSOURCE:
      import os
      import glob
      from pyntcloud import PyntCloud
      from fmeobjects import (FMELogFile,
                              FME_WARN)#FME native logs


      ####READ####

      #read path as string
      bldXYZ = str(FME_MacroValues['tmpXYZbld'])

      #read, get all xyz files in a directory
      list_walls = [PyntCloud.from_file(files,
                                 sep=";",
                                 header=1,
                                 names=["x","y","z"])
                                 for files in glob.glob (bldXYZ + '\*.xyz')]


      #list of xyz file names
      names_walls = [os.path.basename(x) for x in glob.glob(bldXYZ + '\*.xyz')]

      #get range of elements to iterate on
      index = len(list_walls)

      #fire the RANSAC algorithm
      FMELogFile().logMessageString("#--- The RANSAC algorithm has been triggered... ---#", FME_WARN)

      def ransac(feature):

          for i in range (index):

              ###RANSAC###
              # parameter t in RANSAC
              kwargs = {"max_dist": 0.1}

              is_plane = list_walls[i].add_scalar_field("plane_fit", **kwargs)

              ##select point cloud having only inliers (value==1), so-> not equal 0
              selectInliers = list_walls[i].points.loc[list_walls[i].points["is_plane"] == 1]

              ####WRITE####
              #create directory for output files and check if it exists already
              directoryInliers= str(FME_MacroValues['tmpXYZbldInliers'])

              #create one path
              writing_pathInliers = directoryInliers + '/' + names_walls[i]


              #write selected inliers as csv point cloud
              selectInliers.to_csv(writing_pathInliers, index = False, header=True)
    PYTHONSYMBOL = ransac
    -> ListExploder_3
Note: read RANSAC inliers
Note: Adapted from: / https://github.com/tum-gis/CityModelSurgery
FeatureReader_2
    ATTRS_TO_EXPOSE = fme_feature_type
    ATTR_ACCUM_MODE = Merge Initiator and Result
    ATTR_CONFLICT_RES = Use Result
    COMBINE_GEOM = Use Result
    DATASET = @Value(pointcloudXYZnames)
    FORMAT = POINTCLOUDXYZ
    INTERACT = <No Spatial Filter>
    OUTPUT_FEATURES_DISPLAY = Schema and Data Features
    POINTCLOUDXYZ_COLUMN_TO_PCCOMPONENT_HAS_TYPES = yes
    POINTCLOUDXYZ_DUPLICATE_DELIMS = no
    POINTCLOUDXYZ_ENCODING = windows-1252
    POINTCLOUDXYZ_FIELD_NAMES = YES
    POINTCLOUDXYZ_FIELD_NAMES_AFTER_HEADER = no
    POINTCLOUDXYZ_READER_META_ATTRIBUTES = fme_dataset fme_basename
    POINTCLOUDXYZ_SCAN_MAX_LINES = 10000
    POINTCLOUDXYZ_SEPARATOR = auto
    POINTCLOUDXYZ_SKIP_FOOTER = 0
    POINTCLOUDXYZ_SKIP_LINES = 1
    POINTCLOUDXYZ_STRING_DATA_CONTAINS_DELIMS = yes
    POINTCLOUDXYZ_STRIP_QUOTES = no
    POINTCLOUDXYZ_USE_SEARCH_ENVELOPE = NO
    <OTHER> -> StringLengthCalculator

Bookmark: 2.6.2 get writing paths and file names
Note: FeatureWriter outputs a / single report feature / where list attribute keeps / the name of the temp LAS file
ListExploder_3
    ATTR_ACCUM_MODE = Prefix Incoming List
    INCOMING_PREFIX = _ransac_
    INDEX_ATTR = _element_index
    LIST_ATTR = _feature_type{}
    LIST_FOUND -> AttributeExposer_4
AttributeExposer_4
    ATTR_LIST = _ransac_name
    -> AttributeCreator_23
AttributeCreator_23
    ATTR_TABLE = SET_TO pathToInliers = $(tmpXYZbldInliers)
    -> StringConcatenator_2
Note: point cloud .xyz paths
StringConcatenator_2
    ACTION = Create New Attribute
    PARM_LINE = fme_basicstring:21%1%20%4:@Value(pathToInliers)\@Value(_ransac_name).xyz
    VAL_ATTR = pointcloudXYZnames
    -> FeatureReader_2 [INITIATOR]

Bookmark: 2.6.3 Trim str to gml_id back again
StringLengthCalculator
    LENGTH_ATTR = _length
    SRC_ATTR = _ransac_name
    -> ExpressionEvaluator_11
ExpressionEvaluator_11
    ACTION = Create New Attribute
    EXPRESSION = @sub(@Value(_length),2)
    VAL_ATTR = onlyID
    -> StringLengthFormatter
StringLengthFormatter
    Input_Attr = @Value(_ransac_name)
    RESULT_Attr = gml_id
    StringLength = @Value(onlyID)
    -> AttributeRemover_3
AttributeRemover_3
    REMOVE_ATTRS = _length,fme_basename,fme_feature_type,onlyID
    -> PointCloudCombiner_7

Bookmark: 2.6.4 Merge by common building id
Note: merge by gml_id -> object per GML id
PointCloudCombiner_7
    ACCUM_ATTRS_NAME = Yes
    EXTRACT_RASTER_NODATA_NAME = No
    GROUP_BY = gml_id
    SPACING = 1.0
    -> FeatureWriter_2 [File1]

Bookmark: 2.7.1 ensure sequence
GeometryRemover
    -> AttributeKeeper_3
AttributeKeeper_3
    CREATE_BULK_MODE_FEATURES = No
    -> AttributeCreator_22
AttributeCreator_22
    ATTR_TABLE = SET_TO del = 1
    -> FeatureHolder

Bookmark: 2.8.1 get writing paths and file names
Note: FeatureWriter outputs a / single report feature / where list attribute keeps / the name of the temp LAS file
ListExploder_2
    ATTR_ACCUM_MODE = Prefix Incoming List
    INCOMING_PREFIX = _icp_
    INDEX_ATTR = _element_index
    LIST_ATTR = _feature_type{}
    LIST_FOUND -> AttributeExposer_2
AttributeExposer_2
    ATTR_LIST = _icp_name
    -> AttributeCreator_6
AttributeCreator_6
    ATTR_TABLE = SET_TO pathToMatrices = $(rectifiedRotationMatrix)
    -> StringConcatenator_5
Note: point cloud .xyz paths
StringConcatenator_5
    ACTION = Create New Attribute
    PARM_LINE = fme_basicstring:22%1%17%4:@Value(pathToMatrices)\@Value(_icp_name).csv
    VAL_ATTR = rectifMatricesPaths
    -> FeatureReader_3 [INITIATOR]

Bookmark: 2.8 Apply modified ICP
Note: read rectification matrices from ICP algorithm
FeatureReader_3
    ATTRS_TO_EXPOSE = fme_feature_type fme_basename
    ATTR_ACCUM_MODE = Merge Initiator and Result
    ATTR_CONFLICT_RES = Use Result
    COMBINE_GEOM = Use Result
    CSV2_CASE_SENSITIVE_FIELD_NAMES = Yes
    CSV2_CHUNK_SIZE = 100000
    CSV2_DATA_START_LINE = 1
    CSV2_DELIMITER = auto
    CSV2_ENCODING = windows-1250
    CSV2_ENFORCE_STRICT_SCHEMA = No
    CSV2_FEATURE_TYPE_NAME = FORMAT_NAME
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_SKIPPED_LINES = No
    CSV2_SCAN_ADDITIONAL_FIELDS = No
    CSV2_SCAN_MAX_ROWS = 10000
    CSV2_SCAN_TYPES = Yes
    CSV2_SKIP_DUPLICATE_DELIMITERS = No
    CSV2_TRIM_FIELD_NAME_QUALIFIERS = Yes
    CSV2_TRIM_FIELD_VALUE_QUALIFIERS = Yes
    CSV2_USE_CUSTOM_SCHEMA = NO
    DATASET = @Value(rectifMatricesPaths)
    FORMAT = CSV2
    INTERACT = <No Spatial Filter>
    OUTPUT_FEATURES_DISPLAY = Schema and Data Features
    <OTHER> -> AttributeExposer_3
Note: expose matrix rows
AttributeExposer_3
    ATTR_LIST = col0,col1,col2,col3
    -> ListBuilder_2
Note: group by gml id
ListBuilder_2
    GROUP_BY = _icp_name
    LIST_ATTRS_TO_INCLUDE = col0 col1 col2 col3 _icp_name
    LIST_NAME = _list
    -> FeatureMerger_3 [SUPPLIER]
Note: MLS with rectified height
Junction_4
    -> Offsetter_2
Note: offset to the centre of the scene
Offsetter_2
    MODE = Cartesian Coordinate
    XOFF = -@Value(centX)
    YOFF = -@Value(centY)
    ZOFF = -@Value(centMinZ)
    OFFSET -> FeatureMerger_3 [REQUESTOR]
Note: add rectification matrix to respective point clouds per building
FeatureMerger_3
    ATTR_ACCUM_MODE = Merge Supplier
    ATTR_CONFLICT_RES = Use Requestor
    IGNORE_NULLS = No
    JOIN_KEYS = @Value(gml_parent_id) @Value(_icp_name) AUTO
    MERGE_TYPE = Attributes Only
    PROCESS_DUPS = NO
    REJECT_NULL_MISSING_KEYS = No
    SUPPLIERS_FIRST = No
    MERGED -> 3DAffiner
Note: with ground
Note: no Z alteration since Z was fixed before
3DAffiner
    A = @Value(_list{0}.col0)
    B = @Value(_list{0}.col1)
    C = @Value(_list{0}.col2)
    D = @Value(_list{0}.col3)
    E = @Value(_list{1}.col0)
    F = @Value(_list{1}.col1)
    G = @Value(_list{1}.col2)
    H = @Value(_list{1}.col3)
    I = 0
    J = 0
    K = 1
    L = 0
    AFFINED -> Offsetter_7
Note: offset to the centre of the scene
Offsetter_7
    MODE = Cartesian Coordinate
    XOFF = @Value(centX)
    YOFF = @Value(centY)
    ZOFF = @Value(centMinZ)
    OFFSET -> File1 (writer LAS_3)

Bookmark: 3 OUTPUT
Note: rectified point cloud per object (building)
Note: save rectified point cloud
File1 (writer LAS_3)

Bookmark: 2 SYSTEM
Note: only raw walls of buildings

FME custom transformer StringLengthFormatter
Formats attributes to the specified length either truncating or padding the incoming attributes. 
For example, if you set the String Length parameter to 5:
    If an input attribute value consists of only 3 characters, this transformer will add two spaces to the end of the attribute value
    If an input attribute value has a length of 7, this transformer will remove two characters from the end of it
Parameters
    String Length
The desired length of the string to output.
    Source Attribute
Specify the attribute containing the string to reformat.
    Destination Attribute
Specify the name of the attribute to store the reformatted string.

Parameters:
- StringLength = 5   # String length
- Input_Attr =   # Source Attribute
- RESULT_Attr =   # TYPE:varchar(200) Destination Attribute

Input (input)
    -> ParameterFetcher
Note: Retrieve parameters
ParameterFetcher
    ATTR_LIST = _slfLength {$(StringLength)} _slfSource {$(Input_Attr)}
    -> StringLengthCalculator
Note: Determine the input string's length
StringLengthCalculator
    LENGTH_ATTR = _slfSourceLength
    SRC_ATTR = _slfSource
    -> Tester
Note: Check whether input / string is longer than / user's chosen length
Tester
    BOOL_OP = OR
    TEST_CLAUSE = TEST @Value(_slfSourceLength) > @Value(_slfLength)
    TEST_MODE = Automatic
    PASSED -> ExpressionEvaluator
    FAILED -> AttributeCreator
Note: Clean up
AttributeRemover
    REMOVE_ATTRS = $(RESULT_Attr),_slfLength,_slfSource,_slfSourceshrt,_slfSourceLength
    -> Output (output)
Output (output)

Bookmark: If string is longer, remove the extra characters
ExpressionEvaluator
    ACTION = Create New Attribute
    EXPRESSION = @Value(_slfLength)-1
    VAL_ATTR = _slfLength
    -> SubstringExtractor
SubstringExtractor
    END = @Value(_slfLength)
    RESULT_ATTR = $(RESULT_Attr)
    SRC_STRING = @Value(_slfSource)
    START = 0
    -> AttributeRemover

Bookmark: If string is shorter, add extra spaces to the end
AttributeCreator
    ATTR_TABLE = SET_TO $(RESULT_Attr) = @Value(_slfSource)
    -> StringPadder
StringPadder
    BLANK_ATTRIBUTE = Yes
    PADCHAR = " "
    SIDE = Right
    SRC_ATTRS = $(RESULT_Attr)
    WIDTH = @Value(_slfLength)
    -> AttributeRemover

FME custom transformer PercentileCalculator
Calculates upper and lower percentiles of numeric data stored in an attribute.
Description 
A percentile is a statistical measure that marks the value below which a given  percentage  of observations in a set of observations falls. 
This transformer provides a chance to set and calculate upper and lower percentiles for a given numeric dataset that is held in an attribute.
Usage 
Input port 
Input is the data stored in one attribute containing a range of numeric data. 
Parameters 
Select attribute - an attribute in an input dataset. 
Group by - an attribute which may be used to group features and perform percentile calculation per individual group of features. 
Upper percentile - percentile value that is used to indicate and cut off top part of observations in the dataset. 
Lower percentile - percentile value that is used to indicate and cut off bottom part of observations in the dataset. 
Output Ports 
Summary
Body_set
Top_cut-off
Bottom_cut-off
Rejected

Parameters:
- attribute_perc =   # "" Select attribute
- group_attr =   # " " Group by
- upper_percentile = 95   # Upper percentile
- lower_percentile = 5   # Lower percentile

Input (input)
    -> AttributeCreator
AttributeCreator
    ATTR_TABLE:
      SET_TO Percentile_attr = @Value($(attribute_perc))
      SET_TO Sort_attr = @Value($(group_attr))
    -> Tester
Tester
    BOOL_OP = OR
    COMPOSITE_TEST = 1
    TEST_CLAUSE = TEST @Value(Percentile_attr) TYPE NUM
    TEST_MODE = TEST
    PASSED -> Sorter
    FAILED -> Junction
Sorter
    GROUP_BY = Sort_attr
    SORT_PARM = Percentile_attr NUMERIC ASCENDING
    SORTED -> Counter
Counter
    CNT_ATTR = _member
    DOMAIN = @Value(Sort_attr)
    SCOPE = Local
    START = 1
    -> FeatureMerger [REQUESTOR]
    -> Aggregator
    <REJECTED> -> Junction
Aggregator
    ACCUM_ATTRS_NAME = Merge Incoming Attributes
    AGGREGATE_TYPE = Homogeneous Collection (If Possible)
    COUNT_ATTR = Count_agg
    GROUP_BY = Sort_attr
    MODE = Geometry - Assemble One Level
    SEP = ,
    AGGREGATE -> ExpressionEvaluator_4
ExpressionEvaluator_4
    ACTION = Create New Attribute
    EXPRESSION = ($(upper_percentile)/(100))*@Value(Count_agg)
    VAL_ATTR = _upperPercentile
    -> ExpressionEvaluator_2
ExpressionEvaluator_2
    ACTION = Create New Attribute
    EXPRESSION = ($(lower_percentile)/100)*@Value(Count_agg)
    VAL_ATTR = _lowerPercentile
    -> AttributeRounder
AttributeRounder
    PLACES = 0
    ROUND_TYPE = Up
    SRC_ATTRS = _lowerPercentile _upperPercentile
    -> FeatureMerger [SUPPLIER]
FeatureMerger
    ATTR_ACCUM_MODE = Merge Supplier
    ATTR_CONFLICT_RES = Use Requestor
    IGNORE_NULLS = No
    JOIN_KEYS = @Value(Sort_attr) @Value(Sort_attr) AUTO
    MERGE_TYPE = Attributes Only
    PROCESS_DUPS = NO
    REJECT_NULL_MISSING_KEYS = No
    SUPPLIERS_FIRST = No
    MERGED -> TestFilter
    <REJECTED> -> Junction
TestFilter
    DEFAULT_VALUE = <UNFILTERED>
    TEST_LIST = "BOOL_OP,OR,COMPOSITE_TEST,""""""1"""""",TEST_CLAUSE,TEST @Value(_member) > @Value(_upperPercentile)",Top cut-off,"BOOL_OP,OR,COMPOSITE_TEST,""""""1"""""",TEST_CLAUSE,TEST @Value(_member) <= @Value(_lowerPercentile)",Bottom cut-off,"BOOL_OP,OR,COMPOSITE_TEST,""""""1"""""",TEST_CLAUSE,NUM_TEST @Value(_member) RANGE [@Evaluate(@Value(_lowerPercentile)),@Evaluate(@Value(_upperPercentile))]",Body
    Top cut-off -> AttributeRemover_2
    Bottom cut-off -> AttributeRemover
    Body -> AttributeRemover_3
    Body -> StatisticsCalculator
StatisticsCalculator
    COMPUTE_HISTOGRAM = NO
    GROUP_BY = Sort_attr
    MAX_ATTR = _max
    MIN_ATTR = _min
    PREPEND_ATTR_NAME_CHOICE = For multiple results only
    STATS_ATTRS = Percentile_attr
    SUMMARY -> AttributeRenamer
AttributeRenamer
    ATTR_TABLE:
      RENAME_SET_DEFAULT Percentile_attr.min > Lower_percentile
      RENAME_SET_DEFAULT Percentile_attr.max > Upper_percentile
    -> Summary (output)
Summary (output)
AttributeRemover_3
    REMOVE_ATTRS = _lowerPercentile,_upperPercentile,Count_agg,Percentile_attr,Sort_attr
    -> Body_set (output)
Body_set (output)
AttributeRemover_2
    REMOVE_ATTRS = _lowerPercentile,_upperPercentile,Count_agg,Percentile_attr,Sort_attr
    -> Top_cut-off (output)
Top_cut-off (output)
AttributeRemover
    REMOVE_ATTRS = _lowerPercentile,_upperPercentile,Count_agg,Percentile_attr,Sort_attr
    -> Bottom_cut-off (output)
Bottom_cut-off (output)
Junction
    -> Rejected (output)
Rejected (output)
